module oven {
    yang-version 1;
    
    namespace "urn:opendaylight:params:xml:ns:yang:oven";
    
    prefix oven;

    revision "2016-01-13" {
        description "Oven module was initialized on 2016-01-13.";
    }
    
    //declares a base identity, in this case a base type for different types of food.
    identity food-type { //creates a Java base class
      description
        "Base for all food types cooked by the oven. New food types not listed here nay be added in the future.";
    }

    //the below identity section is used to define globally unique identities
    identity cake { //creates Java class that extends the base class generated by photo-type block
      base food-type;       //logically extending the declared toast-type above.
      description "Cooked cake.";  //free text description of this type.
    }

    identity turkey {
      base food-type;
      description "Cooked turkey.";
    }

    identity chicken {
      base food-type;
      description "Cooked chicken.";
    }

    //defines a new "Type" string type which limits the length
    typedef DisplayString { //creates a class DisplayString, with displaystring class variable, length is not mapped 
      type string {
        length "0 .. 255";
      }
      description
        "YANG version of the SMIv2 DisplayString TEXTUAL-CONVENTION.";
      reference
        "RFC 2579, section 2.";
    } // typedef DisplayString
    
    // This definition is the top-level configuration "item" that defines a camera. The "presence" flag connotes there
    // can only be one instance of an oven which, if present, indicates the service is available.
    container oven-params { //creates a Java interface with same name 
      presence
        "Indicates the oven service is available";
      description
        "Top-level container for all oven database objects.";

      //Note in these three attributes that config = false. This indicates that they are operational attributes.
      //all leaf are mapped to getter methods returning type in Camera Java interface
      leaf ovenManufacturer {
        type DisplayString;
        config false;
        mandatory true;
        description
          "The name of the oven's manufacturer. For instance, Miele.";
      } // leaf ovenManufacturer

      leaf ovenModelNumber {
        type DisplayString;
        config false;
        mandatory true;
        description
          "The name of the camera's model. For instance, PureLine M Touch.";
      } // leaf cameraModelNumber
      
      //enum is mapped to Java enum with value as a variable
      leaf ovenStatus {
        type enumeration {
          enum "waiting" {
            value 0;
            description
              "The oven is waiting for commands.";
          }
          enum "preheating" {
            value 1;
            description
              "The oven is preheating. Wait the right temperature to load the food.";
          }
          enum "cooking" {
            value 2;
            description
              "The oven is cooking your food. It will stop at the end of the timer.";
          }
        }
        config false;
        mandatory true;
        description
          "This variable indicates the current state of the oven.";
      } // leaf ovenStatus
      
      leaf ovenMeasureCelsius {
        type boolean;
        default "true";
        config true;
        description
          "This variable indicates if the temperature in the oven is 
           measured in degree Celsius or degree Fahrenheit.
           The measures are made on Clesius on default with the value 'true'.";
      }// leaf ovenMeasureCelsius
      
      leaf ovenEmpty {
        type boolean;
        default "true";
        config true;
        description
          "This variable indicates if the oven is empty or not.
           The oven is empty on default with the value 'true'.";
      }// leaf ovenEmpty
      
      leaf ovenLightOn {
        type boolean;
        default "false";
        config true;
        description
          "This variable indicates if the oven light is on or off.
           The light is turned off on default with the value 'false'.";
      }// leaf ovenLightOn
        
      leaf thermostat {
        type uint16 {
          range "1 .. 7";
        }
        default '7';
        config true;
        description 
          "This variable set the thermostat of the oven, and should be between 1 and 240.";
      } // leaf thermostat
    }  // container oven
    
    rpc cook-food {
      description
        "Choose a program to cook a specified food.";
      input {
        leaf program {
          type identityref {
            base oven:food-type;
          }
          default 'cake';
          description
            "The program helps you to select the best temperature and timer 
             for your type of food to cook. If you enter a program, and no 
             temperature or timer, the program will selects them for you.
             The value should be on the food listm, that can be consult 
             with TODO function. To not choose a program, enter 'none'.";
        } // leaf programm
        
        leaf temperature {
          type uint16 {
            range "90 .. 500";
          }
          default '180';
          description 
            "This variable controls the temperature needed to cook your food.
             It should be on a scale of 90 to 260 in Celsius, or 200 to 500
             if you change the unit of measurement in Fahrenheit.
             Notice that the oven need some time to reach high temperature.";
        } // leaf temperature
        
        leaf timer {
          type uint16 {
            range "1 .. 240";
          }
          default '60';
          description 
            "This variable set the timer of the oven.
             The value is considered in minutes, and should be between 1 and 240.
             Notice that the timer will begin only when the oven has reach 
             the right temperature and when the oven is fill with your food.";
        } // leaf timer
      } // input
    } //rpc cook-food
    
    rpc cancel-program {
     description
       "Stop heating, if any is being cooked.
        A resource-denied error will be returned if the oven service is disabled.";
    } //rpc cancel-program
    
    rpc list-program {
     description
       "Display the list of programs registred in the oven.";
    } //rpc list-program
    
    rpc restock-food {
      description
        "Restock the kitchen with the amount of food needed for the amount of meal specified.";
      input {
        leaf amountOfFoodToStock {
          type uint32;
          description
            "Indicates the amount of food needed to be made available to be clicked.";
        } // leaf amountOfFoodToStock
      } // input
    } // rpc restock-food 
    
    notification kitchenOutOfFood {
      description
        "Indicates that the kitchen has run of food for cooking meal.";
    } // notification kitchenOutOfFood
   

    notification kitchenRestocked {
      description
        "Indicates that the kitchen has been restocked.";
      leaf numberOfMeal {
        type uint32;
        description
          "Indicates the number of meal available to be cooked.";
      }
    }  // notification kitchenRestocked
} // module oven
