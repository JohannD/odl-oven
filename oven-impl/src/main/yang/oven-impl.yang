module oven-impl {

    yang-version 1;
    namespace "urn:opendaylight:params:xml:ns:yang:oven:impl";
    prefix "oven-impl";

    import config { prefix config; revision-date 2013-04-05; }
    import rpc-context { prefix rpcx; revision-date 2013-06-17; }
    import opendaylight-md-sal-binding { prefix mdsal; revision-date 2013-10-28; }

    description
        "Service definition for oven project";

    revision "2016-01-13" {
        description
            "Initial revision";
    }

    identity oven {
        base config:module-type;
        config:java-name-prefix Oven;
    }

   //Wires dependent services into this class - here BindingDataBroker registry service
    augment "/config:modules/config:module/config:configuration" {
        case oven {
            when "/config:modules/config:module/config:type = 'oven'";
            container broker {
                uses config:service-ref {
                    refine type {
                        mandatory true;
                        config:required-identity mdsal:binding-broker-osgi-registry;
                    }
                }
            }
            //Wires dependent services into this class - in this case the RPC registry service
            container rpc-registry {
                uses config:service-ref {
                    refine type {
                        mandatory true;
                        config:required-identity mdsal:binding-rpc-registry;
                    }
                }
            }
            //Wires CameraProvider to Notification service
            container notification-service {
               uses config:service-ref {
                   refine type {
                       mandatory true;
                       config:required-identity mdsal:binding-notification-service;
                   }
                }
            }
        }
    } // augment configuration
    
    augment "/config:modules/config:module/config:state" {
        case oven {
            when "/config:modules/config:module/config:type = 'oven'";
            leaf meal-cooked {
                type uint32;
            }
            rpcx:rpc-context-instance "clear-meal-cooked-rpc";
        }
    } // augment state
    identity clear-meal-cooked-rpc;
    //rpc clear-meal-cooked  {
    rpc clear-meal-cooked-rpc  {
        description
          "JMX call to clear the meal-cooked counter.";

        input {
            uses rpcx:rpc-context-ref {
                refine context-instance {
                    rpcx:rpc-context-instance clear-meal-cooked-rpc;
                }
            }
        }
    } // rpc state
} // module oven-imp
